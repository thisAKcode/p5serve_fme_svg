FME workspace lines_rotated_v2.fmw

Parameters:
- DestDataset_SVG = .\asset.svg   # Destination SVG (ScalableVectorGraphics) File

Writers:
- SVG_1: SVG to $(DestDataset_SVG)

Note: credits: / Gin / https://note.com/gin_graphic/n/n5237b5e3f080
asset (writer SVG_1)
    attributes: _count largeint, _x float, _y float, _z float, i char(254)

Bookmark: iteratively build line sequences with start point placed on grid
PythonCreator
    NEW_ATTRIBUTES = _count int64
    PYTHONSOURCE_NEW:
      import fmeobjects

      num_points = 20
      _offset = 200

      class FeatureCreator(object):


          def __init__(self):
              """Base constructor for class members."""
              pass

          def input(self, feature: fmeobjects.FMEFeature):
              """create kind a grid of points
              """
              grid = { n + 1:
                      (
                      (n % 5) * _offset,  # (n %  5):  0-based column *offset = X coord
                      (n // 5) * _offset  # (n // 5):  0-based row   * offset = Y coord
                      )
                      for n in range(num_points)
                      }
              for _count,j in grid.items():
                  newFeature = fmeobjects.FMEFeature()
                  newFeature.setAttribute('_count', int(_count))
                  point = fmeobjects.FMEPoint()
                  point.setXYZ(float(j[0]), float(j[1]), 0)

                  newFeature.setGeometry(point)
                  self.pyoutput(newFeature)

          def close(self):
              """This method is called at the end of the class."""
              pass
    PYTHONSYMBOL = FeatureCreator
    -> CoordinateExtractor
CoordinateExtractor
    IND = 0
    RECURSIVE = No
    X_ATTR = _x
    Y_ATTR = _y
    Z_ATTR = _z
    MODE = Specify Coordinate
    -> PythonCaller_4
PythonCaller_4
    NEW_ATTRIBUTES = i buffer
    PYTHONSOURCE:
      #main_script
      import fme
      import fmeobjects
      import numpy as np
      import random
      import math
      from fmeobjects import FMELine, FMEGeometryTools


      def _line_maker(start_x, start_y, _length, num_pts):
          array_x, array_y = [],[]
          _lines = []
          for i in range(num_pts):
              TAU = 2 * math.pi
              angle = TAU / num_pts * i

              array_x.append(start_x + _length * math.cos(angle))
              array_y.append(start_y + _length * math.sin(angle))

          for i in range(num_pts):
              obj1 = [(array_x[i], array_y[i]), (array_x[(i+1) % num_pts], array_y[(i+1) % num_pts])]
              _lines.append(obj1)

          return _lines


      class FeatureProcessor(object):


          def __init__(self):
              pass

          def has_support_for(self, support_type: int):
              return support_type == fmeobjects.FME_SUPPORT_FEATURE_TABLE_SHIM

          def input(self, feature: fmeobjects.FMEFeature):
              x, y = feature.getAttribute('_x'), feature.getAttribute('_y')
              edge_num = feature.getAttribute('_count')
              lines  = _line_maker(x, y, 100, edge_num)
              for i in lines:
                  feature.setAttribute('i', str(i))
                  line = FMELine(i)
                  feature.setGeometry(line)

                  self.pyoutput(feature)

          def close(self):

              pass

          def process_group(self):

              pass
    PYTHONSYMBOL = FeatureProcessor
    -> Bufferer_2
Bufferer_2
    ANGLE = 22.5
    CAP_STYLE_LOOKUP = CAP_ROUND
    CORNER_STYLE_LOOKUP = JOIN_ROUND
    MODE = AREA
    OFFSET = 2
    OFFSET_UNITS = NONE
    PRECISION = APPROX
    CAP_STYLE = Round
    CORNER_STYLE = Round
    BUFFERED -> asset (writer SVG_1)
