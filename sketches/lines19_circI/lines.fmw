FME workspace lines.fmw
Startup Python:
      import fme
      print(dir(fme))

Parameters:
- DestDataset_SVG = .\asset.svg   # Destination SVG (ScalableVectorGraphics) File

Writers:
- SVG_1: SVG to $(DestDataset_SVG)

Creator
    GEOMTYPE = Geometry Object
    NUM = 1
    CREATED -> PythonCaller_4
Note: node garden
PythonCaller_4
    NEW_ATTRIBUTES = i varchar(20000)
    PYTHONSOURCE:
      #main_script
      import fmeobjects
      import numpy as np
      from fmeobjects import FMELine, FMEPoint, FMEPolygon
      import numpy as np

      def node_garden_ring(n=10, r=1.0, thresh=0.4):
          a = np.linspace(0, 2*np.pi, n, endpoint=False)
          pts = np.c_[r*np.cos(a), r*np.sin(a)]
          lines = []

          for i in range(n):
              for j in range(i+1, n):
                  d = np.linalg.norm(pts[i] - pts[j])
                  if d < thresh:
                      lines.append((tuple(pts[i]), tuple(pts[j])))

          return pts, lines

      class FeatureProcessor(object):
          def __init__(self):
              pass

          def input(self, feature: fmeobjects.FMEFeature):
              nodes, lines = node_garden_ring(n=21, r=1.0, thresh=1.8)
              # output the star boundary
              for line in lines:
                  print(line)
                  tri_ring = (list(map(tuple, line)))
                  tri_line = FMELine([tuple(p) for p in tri_ring])
                  out_feat = fmeobjects.FMEFeature(feature)
                  out_feat.setGeometry(tri_line)
                  self.pyoutput(out_feat)
    PYTHONSYMBOL = FeatureProcessor
    -> GeometryFilter
GeometryFilter
    FILTER_MODE = SIMPLE
    FILTER_MULTI = FILTER_TYPES]Line Area]FILTER_TYPES_Simple]Line Area
    FILTER_TYPES = Line Area
    FILTER_TYPES_Simple = Line Area
    Curve -> Bufferer
    Curve -> test (writer SVG_1)
    Area -> Bufferer
Bufferer
    ANGLE = 22.5
    CAP_STYLE_LOOKUP = CAP_ARC
    CORNER_STYLE_LOOKUP = JOIN_ARC
    MODE = AREA
    OFFSET = 0.01
    OFFSET_UNITS = NONE
    PRECISION = APPROX
    CAP_STYLE = Arc
    CORNER_STYLE = Arc
    BUFFERED -> test (writer SVG_1)
test (writer SVG_1)
    attributes: _creation_instance decimal(20,0), i char(20000)
