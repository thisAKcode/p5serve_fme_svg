FME workspace lines_from_image.fmw

Parameters:
- DestDataset_SVG = .\test.svg   # Destination SVG (ScalableVectorGraphics) File

Writers:
- SVG_1: SVG to $(DestDataset_SVG)

Creator
    GEOMTYPE = Geometry Object
    NUM = 1
    CREATED -> PythonCaller_4
Note: image made of zickzacks / try to swap order in which x and y placed in nested loops
PythonCaller_4
    NEW_ATTRIBUTES = foo buffer
    PYTHONSOURCE:
      #main_script
      import fme
      import fmeobjects
      import random
      import math
      import matplotlib.pyplot as plt
      import numpy as np
      from PIL import Image
      from fmeobjects import FMELine


      grid_cnt = 5
      num_points = 20
      _offset = 200
      unit = 15
      half_unit = int(unit / 2)
      _path = r'C:\p5serve_fme_svg\sketches\_6_only_lines'
      _imagename = 'image.png'
      # load image _imagename from _path
      img = Image.open(f'{_path}/{_imagename}')
      img= img.transpose(Image.Transpose.FLIP_TOP_BOTTOM)
      pixelColor = img.getpixel((10, 10))
      image_width, image_height = img.size
      # image_height, image_width = image.shape[:2]

      width, height = image_width, image_height

      def map(value, left_min, left_max, right_min, right_max):
          # Figure out how 'wide' each range is
          left_span = left_max - left_min
          right_span = right_max - right_min
          # Convert the left range into a 0-1 range (float)
          value_scaled = float(value - left_min) / float(left_span)
          # Convert the 0-1 range into a value in the right range.
          return right_min + (value_scaled * right_span)


      class FeatureProcessor(object):

          def __init__(self):
              pass

          def _create_and_output_line(self, start_point, end_point, attributes):
              line = FMELine()
              line.appendPoint((start_point[0], start_point[1], 0))
              line.appendPoint((end_point[0], end_point[1], 0))

              lineFeature = fmeobjects.FMEFeature()
              lineFeature.setAttribute('foo',attributes)
              lineFeature.setGeometry(line)
              self.pyoutput(lineFeature)

          def input(self, feature: fmeobjects.FMEFeature):
              grid = { n + 1:
                      (
                      (n % 5) * _offset + (_offset * random.uniform(0.5, 1)),  # (n %  5):  0-based column *offset = X coord
                      (n // 5) * _offset + (_offset * random.uniform(0.5, 1))# (n // 5):  0-based row   * offset = Y coord
                      )
                      for n in range(num_points)
                      }
              # Get image size
              image_width, image_height = img.size
              line_counter= 0
              for x in range(0, width, half_unit):
                  for y in range(0, height, unit):
                      pixelColor = img.getpixel((x, y))
                      gray = (pixelColor[0] + pixelColor[1] + pixelColor[2]) / 3
                      size = map(gray, left_min=0, left_max=255, right_min=0, right_max=half_unit)
                      if line_counter%2 == 0:
                          start_point = (x,y)
                          end_point= (x-half_unit, y +unit)
                          self._create_and_output_line(start_point, end_point,size)
                      else:
                          start_point = (x-half_unit, y)
                          end_point= (x, y+unit)
                          self._create_and_output_line(start_point, end_point, size)
                  line_counter +=1


          def close(self):
              pass

          def process_group(self):

              pass
    PYTHONSYMBOL = FeatureProcessor
    -> Bufferer_4
Bufferer_4
    ANGLE = 22.5
    CAP_STYLE_LOOKUP = CAP_PROJECTING
    CORNER_STYLE_LOOKUP = JOIN_ARC
    MODE = AREA
    OFFSET = @Value(foo)
    OFFSET_UNITS = NONE
    PRECISION = APPROX
    CAP_STYLE = Square
    CORNER_STYLE = Arc
    BUFFERED -> GeometryFilter
GeometryFilter
    FILTER_MODE = SIMPLE
    FILTER_MULTI = FILTER_TYPES]Area]FME_CONTROLLER_QUERY_FILE]]FME_CONTROLLER_CHOICE]Simple
    Area -> Extruder
Extruder
    DIRECTION_LOOKUP = AUTO
    DISTANCE = 10
    DIRECTION = Auto
    EXTRUDED -> test (writer SVG_1)
test (writer SVG_1)
    attributes: _creation_instance decimal(20,0), foo char(254)

Bookmark: raster mathplotlib
Note: # image made of zickzacks / import numpy as np / import random / import math / import matplotlib.pyplot as plt / import fme / import fmeobjects / from fmeobjects import FMELine / _path = r'C:\p5serve_fme_svg\_6_only_lines' / _imagename = 'image.png' / # load image _imagename from _path / image = plt.imread(f'{_path}/{_imagename}') / image_height, image_width = image.shape[:2] / width, height = image_width, image_height / print(width,height) / grid_cnt = 5 / num_points = 20 / _offset = 200 / def get_pixel_value(image, x, y): / return image[x,y] / unit = 15 / half_unit = int(unit / 2) / def map(value, left_min, left_max, right_min, right_max): / # Figure out how 'wide' each range is / left_span = left_max - left_min / right_span = right_max - right_min / # Convert the left range into a 0-1 range (float) / value_scaled = float(value - left_min) / float(left_span) / # Convert the 0-1 range into a value in the right range. / return right_min + (value_scaled * right_span) / class FeatureProcessor(object): / def __init__(self): / pass / def _create_and_output_line(self, start_point, end_point, attributes): / line = FMELine() / line.appendPoint((start_point[0], start_point[1], 0)) / line.appendPoint((end_point[0], end_point[1], 0)) / lineFeature = fmeobjects.FMEFeature() / lineFeature.setAttribute('foo',attributes) / lineFeature.setGeometry(line) / self.pyoutput(lineFeature) / def input(self, feature: fmeobjects.FMEFeature): / grid = { n + 1: / ( / (n % 5) * _offset + (_offset * random.uniform(0.5, 1)), # (n % 5): 0-based column *offset = X coord / (n // 5) * _offset + (_offset * random.uniform(0.5, 1))# (n // 5): 0-based row * offset = Y coord / ) / for n in range(num_points) / } / # Get image size / image_height, image_width = image.shape[:2] / line_counter= 0 / for x in range(0, height, half_unit): / for y in range(0, width, unit): / pixelColor = get_pixel_value(image, x, y) / gray = (pixelColor[0]*255 + pixelColor[1]*255 + pixelColor[2]*255) / 3 / # size = round(map(gray, 0, 255, 0, half_unit)) / size = map(gray, left_min=0, left_max=255, right_min=0, right_max=half_unit) / line_counter +=1 / #strokeWeight(size); / if line_counter%2 == 0: / start_point = (x,y) / end_point= (x-half_unit, y +unit) / self._create_and_output_line(start_point, end_point,size) / else: / start_point = (x-half_unit, y) / end_point= (x, y+unit) / self._create_and_output_line(start_point, end_point, size) / def close(self): / """This method is called once all the FME Features have been processed from input().""" / pass / def process_group(self): / pass / In matplotlib, the origin (0, 0) is at the top-left corner by default. This differs from FME where the origin might be bottom-left.
