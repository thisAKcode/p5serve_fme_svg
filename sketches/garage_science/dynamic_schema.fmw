FME workspace dynamic_schema.fmw

Parameters:
- SourceDataset_SHAPEFILE_2 = $(FME_MF_DIR)data\ports.shp   # Source Esri Shapefile(s)
- DestDataset_SHAPEFILE = $(FME_MF_DIR)data   # Destination Esri Shapefile Folder

Readers:
- SHAPEFILE_3: SHAPEFILE from $(SourceDataset_SHAPEFILE_2)

Writers:
- SHAPEFILE_1: SHAPEFILE to $(DestDataset_SHAPEFILE)

Note: https://www.naturalearthdata.com/http//www.naturalearthdata.com/download/10m/cultural/ne_10m_ports.zip
ports (reader SHAPEFILE_3)
    attributes: scalerank long, featurecla varchar(80), name varchar(50), website varchar(254), natlscale double, ne_id number(11,0)
    -> SchemaScanner
SchemaScanner
    CASE = No
    EMPTY_ATTR_HANDLING = IGNORE
    HOLD = Yes
    NUMERIC_ALLOW_LEADING_ZEROES = Yes
    SCHEMA_NAME_ATTR = fme_feature_type_name
    UNBOUNDED_NUMBERS = Yes
    UNBOUNDED_STRINGS = No
Creator
    GEOMTYPE = Geometry Object
    NUM = 1
    CREATED -> FeatureReader [INITIATOR]
FeatureReader
    ATTR_ACCUM_MODE = Only Use Result
    COMBINE_GEOM = Use Result
    DATASET = $(FME_MF_DIR_ENCODED)data\ports.shp
    FORMAT = SHAPEFILE
    INTERACT = NONE
    ORDER_RESULTS = No
    OUTPUT_ADD_SCHEMA_ATTRIBUTES = NO
    OUTPUT_FEATURES_DISPLAY = Schema and Data Features
    SHAPEFILE_ALLOW_MISMATCHED_SHZ_BASENAME = No
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    <SCHEMA> -> AttributeExposer
    <OTHER> -> AttributeExposer
    <OTHER> -> foo
foo
    ForceDataType = No
    SORT = None
AttributeExposer
    ATTR_TABLE = fme_feature_type,
    -> AttributeManager
AttributeManager
    ATTR_TABLE = SET_TO fme_feature_type (varchar(13)) = ports_dynamic
    -> Shapefile1 (writer SHAPEFILE_1)
Note: https://community.safe.com/data-7/reading-multiple-shp-files-with-the-featurereader-and-dynamically-exposing-all-attributes-17320
Shapefile1 (writer SHAPEFILE_1)

FME custom transformer foo
test

Parameters:
- AttributesToExclude =   # " " Attributes to exclude
- PrefixesToExclude =   # Prefixes to exclude
- SORT = None   # Sort Attributes
- ForceDataType = No   # Force attributes to strings?

Input (input)
    -> ParameterFetcher
Note: Retrieve Parameters
ParameterFetcher
    ATTR_LIST = _AttributesToExclude $(AttributesToExclude) _PrefixesToExclude $(PrefixesToExclude) _sort $(SORT) _ForceDataType $(ForceDataType)
    -> PythonCaller
Note: See Comment in Code
PythonCaller
    PYTHONSOURCE:
      from __future__ import absolute_import, division, print_function, unicode_literals

      import fmeobjects
      import six

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedAttributes.append('_ForceDataType')
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              # sorting attributes
              if feature.getAttribute('_sort') == 'Ascending' or feature.getAttribute('_sort') == 'Descending':
                  attlist.sort()
                  if feature.getAttribute('_sort') == 'Descending':
                      attlist.reverse()

              for att in attlist:
                  if not StringInList(ExcludedAttributes,att) and not StringLikeList(ExcludedPrefixes,att) and not att=='_AttributesToExclude' and not att=='_PrefixesToExclude' and not att=='_sort':

                     #Check datatype and set in schema
                     if feature.getAttribute('_ForceDataType') == 'No':
                         type = feature.getAttributeType(att)
                         type = self.typesMapping[type]
                     #Force to string if user wishes
                     else:
                         type = "fme_char(255)"

                     if type is None:
                         feature.removeAttribute(att)
                     else:
                         #add schema attributes to feature
                         nfeature.setAttribute("attribute{"+str(i)+"}.fme_data_type",type)
                         nfeature.setAttribute("attribute{"+str(i)+"}.name",six.text_type(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              self.pyoutput(nfeature)
          def close(self):
              pass
    PYTHONSYMBOL = FeatureProcessor
    -> Output (output)
Output (output)
