FME workspace lines_rotated.fmw

Parameters:
- DestDataset_SVG = .\asset.svg   # Destination SVG (ScalableVectorGraphics) File

Writers:
- SVG_1: SVG to $(DestDataset_SVG)

Note: credits: / Gin / https://note.com/gin_graphic/n/n5237b5e3f080
asset (writer SVG_1)
    attributes: _creation_instance decimal(20,0), _count largeint, i char(254)

Bookmark: iteratively build overlaying line sequences on same start point.
Creator_2
    GEOMTYPE = Geometry Object
    NUM = 20
    CREATED -> Counter
Counter
    CNT_ATTR = _count
    DOMAIN = counter
    SCOPE = Global
    START = 1
    -> PythonCaller
PythonCaller
    NEW_ATTRIBUTES = i buffer
    PYTHONSOURCE:
      #main_script
      import fme
      import fmeobjects
      import numpy as np
      import random
      import math
      from fmeobjects import FMELine, FMEGeometryTools


      def _line_maker(start_x, start_y, _length, num_pts):
          array_x, array_y = [],[]
          _lines = []
          for i in range(num_pts):
              TAU = 2 * math.pi
              angle = TAU / num_pts * i

              array_x.append(start_x + _length * math.cos(angle))
              array_y.append(start_y + _length * math.sin(angle))

          for i in range(num_pts):
              obj1 = [(array_x[i], array_y[i]), (array_x[(i+1) % num_pts], array_y[(i+1) % num_pts])]
              _lines.append(obj1)

          return _lines


      class FeatureProcessor(object):


          def __init__(self):
              pass

          def has_support_for(self, support_type: int):
              return support_type == fmeobjects.FME_SUPPORT_FEATURE_TABLE_SHIM

          def input(self, feature: fmeobjects.FMEFeature):
              edge_num = feature.getAttribute('_count')
              lines  = _line_maker(0, 0, 100, edge_num)
              for i in lines:
                  feature.setAttribute('i', str(i))
                  line = FMELine(i)
                  feature.setGeometry(line)

                  self.pyoutput(feature)

          def close(self):

              pass

          def process_group(self):

              pass
    PYTHONSYMBOL = FeatureProcessor
    -> Bufferer
Bufferer
    ANGLE = 22.5
    CAP_STYLE_LOOKUP = CAP_ROUND
    CORNER_STYLE_LOOKUP = JOIN_ROUND
    MODE = AREA
    OFFSET = 2
    OFFSET_UNITS = NONE
    PRECISION = APPROX
    CAP_STYLE = Round
    CORNER_STYLE = Round
    BUFFERED -> asset (writer SVG_1)
