FME workspace lines_rotated.fmw

Parameters:
- DestDataset_SVG = .\test.svg   # Destination SVG (ScalableVectorGraphics) File

Writers:
- SVG_1: SVG to $(DestDataset_SVG)

test (writer SVG_1)
    attributes: angle smallint, segment_size largeint, ID largeint
Note: THIS BLOG POST / IS 80% / AI-FREE. / REAL HANDS / WERE SHAKING / COUPLE OF TIMES
AttributeCreator_4
    ATTR_TABLE = SET_TO angle (uint8) = 30

Bookmark: make a perlin-noise-line
PythonCreator_2
    PYTHONSOURCE_NEW:
      import fmeobjects
      import math
      import random

      def fade(t):
          """Smoothstep for interpolation."""
          return t * t * t * (t * (t * 6 - 15) + 10)

      def lerp(a, b, t):
          """Linear interpolation."""
          return a + t * (b - a)

      def gradient(hash, x):
          """gradient hash-based."""
          return (hash & 1) * 2 - 1

      def perlin_noise(x, perm):
          """1D Perlin noise function."""
          xi = int(math.floor(x)) & 255  # Wrap around 256
          xf = x - math.floor(x)         # Fractional part
          u = fade(xf)

          # Hash the coordinates
          g1 = perm[xi]
          g2 = perm[xi + 1]

          # Gradient values
          n1 = gradient(g1, xf)
          n2 = gradient(g2, xf - 1)

          return lerp(n1, n2, u)

      def generate_random_line(length, scale):
          """Generate a random line using Perlin noise as a list of (x, y) tuples."""
          perm = [i for i in range(256)]
          random.shuffle(perm)
          perm += perm  # Extend for wrap-around

          # Use a generator for large lengths to reduce memory usage
          return ((x, perlin_noise(x / scale, perm)) for x in range(length))
      length = 100
      scale = 10 # length * 0.1
      line = generate_random_line(length, scale)


      class FeatureCreator(object):

          def __init__(self):
              pass

          def input(self, feature: fmeobjects.FMEFeature):
              _lino = fmeobjects.FMELine()
              for vertex in line:
                  point = fmeobjects.FMEPoint()
                  point.setXYZ(float(vertex[0])*100, float(vertex[1])*100, 0)
                  _lino.appendPoint(point)
                  # shorter_link = FMELine([(x0,y0),(x2,y2)])
              newFeature = fmeobjects.FMEFeature()
              newFeature.setGeometry(_lino)
              self.pyoutput(newFeature)

          def close(self):
              """This method is called at the end of the class."""
              pass
    PYTHONSYMBOL = FeatureCreator
    -> AttributeCreator
AttributeCreator
    ATTR_TABLE = SET_TO segment_size (int64) = 1000
    -> PythonCaller_2
Note: split line
PythonCaller_2
    NEW_ATTRIBUTES = ID int64
    PYTHONSOURCE:
      import fme
      import fmeobjects
      import numpy as np


      def segment_generator(length, segment_size):
          # lazy way to generate sequence
          for start in np.arange(0, length, segment_size):
              yield (start, min(start + segment_size, length))


      class FeatureProcessor(object):


          def __init__(self):

              pass

          def has_support_for(self, support_type: int):

              return support_type == fmeobjects.FME_SUPPORT_FEATURE_TABLE_SHIM

          def input(self, feature: fmeobjects.FMEFeature):
              # get line length
              # Example usage
              length = int(float(feature.performFunction('@Length(2)'))) # 2D Length
              segment_size = feature.getAttribute('segment_size')
              segments = list(segment_generator(length, segment_size))

              for _count, item in enumerate(segments):
                  _clone = feature.clone()
                  _clone.performFunction(f"@Snip({int(item[0])}, {int(item[1])}, 1)")
                  _clone.setAttribute('ID',_count)
                  self.pyoutput(_clone)
                  # self.pyoutput(feature)

          def close(self):

              pass

          def process_group(self):
              pass
    PYTHONSYMBOL = FeatureProcessor
    -> AttributeCreator_3
    -> AttributeCreator_2
    -> AttributeCreator_5
AttributeCreator_3
    ATTR_TABLE = SET_TO angle (uint8) = 30
    -> PythonCaller_4
AttributeCreator_2
    ATTR_TABLE = SET_TO angle (uint8) = 60
    -> PythonCaller_4
AttributeCreator_5
    ATTR_TABLE = SET_TO angle (uint8) = 90
    -> PythonCaller_4
Note: compute bearing output perpendiculars
PythonCaller_4
    PYTHONSOURCE:
      #main_script
      import fme
      import fmeobjects
      import math

      def compute_second_point(start_point, bearing, distance):
          x1, y1 = start_point

          # Convert bearing to radians
          bearing_rad = math.radians(bearing)

          # Calculate delta x and delta y
          dx = distance * math.sin(bearing_rad)
          dy = distance * math.cos(bearing_rad)

          # Compute second point
          x2 = x1 + dx
          y2 = y1 + dy

          return (x2, y2)

      def compute_bearing(x0,y0,x1,y1):
          # Calculate differences
          delta_x = x1- x0
          delta_y = y1 - y0

          # Calculate the angle in radians
          theta = math.atan2(delta_x, delta_y)

          # Convert to degrees and ensure the angle is within [0, 360)
          bearing = (math.degrees(theta) + 360) % 360

          return bearing


      class FeatureProcessor(object):


          def __init__(self):
              pass

          def input(self, feature: fmeobjects.FMEFeature):
              # grab parameters to make the "ribs"
              distance = feature.getAttribute('segment_size')
              angle = feature.getAttribute('angle')
              id = feature.getAttribute('ID')
              x0,y0,z0 = feature.getGeometry().getStartPoint().getXYZ()
              x1,y1,z1 = feature.getGeometry().getEndPoint().getXYZ()
              bearing = compute_bearing(x0,y0,x1,y1)
              start_point = (x1,y1)
              start_point_fme = fmeobjects.FMEPoint(x1,y1)

              # right side rib
              outpt_r = compute_second_point(start_point, bearing+ angle, distance)
              newFeature = fmeobjects.FMEFeature()
              line_r = fmeobjects.FMELine([start_point, outpt_r])
              # line_r.copyAttributesFromFeature(feature, True)
              newFeature.setGeometry(line_r)
              newFeature.setAttribute('ID',id)
              self.pyoutput(feature)
              self.pyoutput(newFeature)


              # left side rib
              outpt_l = compute_second_point(start_point, bearing- angle, distance)
              newFeature = fmeobjects.FMEFeature()
              line_l = fmeobjects.FMELine([start_point, outpt_l])
              # line_l.copyAttributesFromFeature(feature, True)
              newFeature.setGeometry(line_l)
              newFeature.setAttribute('ID',id)
              self.pyoutput(feature)
              self.pyoutput(newFeature)

          def close(self):
              pass

          def process_group(self):
              pass
    PYTHONSYMBOL = FeatureProcessor
    -> test (writer SVG_1)
