FME workspace lines.fmw
Startup Python:
      import fme
      print(dir(fme))

Parameters:
- DestDataset_SVG = .\asset.svg   # Destination SVG (ScalableVectorGraphics) File

Writers:
- SVG_1: SVG to $(DestDataset_SVG)

Creator
    GEOMTYPE = Geometry Object
    NUM = 1
    CREATED -> PythonCaller_4
Note: node garden
PythonCaller_4
    NEW_ATTRIBUTES = i varchar(20000)
    PYTHONSOURCE:
      #main_script
      import fmeobjects
      import numpy as np
      from fmeobjects import FMELine, FMEPoint, FMEPolygon
      import numpy as np
      import math


      """
      radial lines across the center
      *  <pipe>  *
       \ <pipe> /
        \<pipe>/
        /<pipe>\
       / <pipe> \
      *  <pipe>  *

      next time connect symmetric indices
      0  1  2  3  4 ... n/2
      <pipe>              <pipe>
      n-1        n/2+1
      """

      def radial_ring_lines(n=36, w=800, h=800):
          r=min(w,h)*0.4
          p=[(r*math.cos(2*math.pi*i/n), r*math.sin(2*math.pi*i/n)) for i in range(n)]
          return [(p[i], p[i+n//2]) for i in range(n//2)]


      def ring_lines(n=36, w=800, h=800):
          r = min(w, h)*0.4
          pts = [(r*math.cos(2*math.pi*i/n),
                  r*math.sin(2*math.pi*i/n)) for i in range(n)]
          lines = [(pts[i], pts[(i+1)%n]) for i in range(n)]
          return pts,lines

      class FeatureProcessor(object):
          def __init__(self):
              pass

          def input(self, feature: fmeobjects.FMEFeature):
              pts, lines = ring_lines(n=36, w=800, h=800)
              # output the star boundary
              for line in lines:
                  print(line)
                  tri_ring = (list(map(tuple, line)))
                  tri_line = FMELine([tuple(p) for p in tri_ring])
                  out_feat = fmeobjects.FMEFeature(feature)
                  out_feat.setGeometry(tri_line)
                  self.pyoutput(out_feat)
              parallel_lines = radial_ring_lines(n=36, w=800, h=800)

              for pline in parallel_lines:
                  tri_ring = (list(map(tuple, pline)))
                  tri_line = FMELine([tuple(p) for p in tri_ring])
                  out_feat = fmeobjects.FMEFeature(feature)
                  out_feat.setGeometry(tri_line)
                  self.pyoutput(out_feat)
    PYTHONSYMBOL = FeatureProcessor
    -> GeometryFilter
GeometryFilter
    FILTER_MODE = SIMPLE
    FILTER_MULTI = FILTER_TYPES]Line Area]FILTER_TYPES_Simple]Line Area
    FILTER_TYPES = Line Area
    FILTER_TYPES_Simple = Line Area
    Curve -> Bufferer
    Curve -> test (writer SVG_1)
    Area -> Bufferer
Bufferer
    ANGLE = 22.5
    CAP_STYLE_LOOKUP = CAP_ARC
    CORNER_STYLE_LOOKUP = JOIN_ARC
    MODE = AREA
    OFFSET = 2
    OFFSET_UNITS = NONE
    PRECISION = APPROX
    CAP_STYLE = Arc
    CORNER_STYLE = Arc
    BUFFERED -> test (writer SVG_1)
test (writer SVG_1)
    attributes: _creation_instance decimal(20,0), i char(20000)
